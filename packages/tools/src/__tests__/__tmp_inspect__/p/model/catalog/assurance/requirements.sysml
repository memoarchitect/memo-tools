package project_assurance {
    private import memo::*;

    requirement mainRequirement : Requirement {
        attribute redefines statement = "TODO: state the first system requirement.";
        doc /* TODO: define the first system requirement. */
    }
}
